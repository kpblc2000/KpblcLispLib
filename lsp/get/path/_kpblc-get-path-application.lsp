(defun _kpblc-get-path-application ()
                                   ;|
  *    Возвращает родительский каталог для приложения (в текущей реализации - %AppData%\kpblcLib)
  |;
  (strcat (_kpblc-dir-path-and-splash (_kpblc-get-path-root-appdata)) "KpblcLib")
) ;_ end of defun
