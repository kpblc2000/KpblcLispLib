(defun _kpblc-dcl-create-title-label (title)
                                     ;|
			*    Создание заголовка для dcl-диалга
			*    Параметры вызова:
			  title  ; Выводимое сообщение
			|;
  (strcat "\"" title "\"")
) ;_ end of defun
