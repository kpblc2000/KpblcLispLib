(defun _kpblc-is-ent-document (ent)
                              ;|
*    Проверяет, является ли переданный параметр указателем на документ
*    Параметры вызова:
  ent    vla-указатель. nil -> считается, что проверяется "активный" документ
*    Возвращает либо vla-указатель на документ, либо nil для ошибки.
|;
  (cond ((not ent) *kpblc-adoc*)
        ((equal ent *kpblc-adoc*) ent)
        ((and (= (type ent) 'vla-object) (vlax-property-available-p ent 'modelspace)) ent)
  ) ;_ end of cond
) ;_ end of defun
